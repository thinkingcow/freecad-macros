import FreeCAD
import FreeCADGui
import Part
import math
import bisect
import sys

class EllipticalGear:
    """Parametric Elliptical Gear Object for FreeCAD 1.1"""
    def __init__(self, obj):
        obj.Proxy = self
        
        # ----------------------------------------------------
        # 1. USER-MODIFIABLE PROPERTIES
        # ----------------------------------------------------
        obj.addProperty("App::PropertyInteger", "Teeth", "Gear", "Number of teeth (Z)").Teeth = 30
        obj.addProperty("App::PropertyFloat", "AspectRatio", "Gear", "Ratio of semi-major to semi-minor axis (a/b)").AspectRatio = 1.25
        obj.addProperty("App::PropertyFloat", "Module", "Gear", "Gear module in mm (m)").Module = 2.0
        obj.addProperty("App::PropertyFloat", "Thickness", "Gear", "Gear face thickness in mm").Thickness = 10.0
        obj.addProperty("App::PropertyAngle", "PressureAngle", "Gear", "Pressure angle").PressureAngle = 20.0
        
        # Bore hole properties
        obj.addProperty("App::PropertyFloat", "BoreRadius", "Bore", "Center bore hole radius in mm").BoreRadius = 10.0
        obj.addProperty("App::PropertyFloat", "FocusBore1Radius", "Bore", "Focus 1 hole radius in mm (-c, 0)").FocusBore1Radius = 0.0
        obj.addProperty("App::PropertyFloat", "FocusBore2Radius", "Bore", "Focus 2 hole radius in mm (+c, 0)").FocusBore2Radius = 0.0

        # ----------------------------------------------------
        # 2. READ-ONLY CALCULATED PROPERTIES
        # ----------------------------------------------------
        obj.addProperty("App::PropertyLength", "MajorOutsideDiameter", "Gear Dimensions", "Outside major axis diameter")
        obj.addProperty("App::PropertyLength", "MinorOutsideDiameter", "Gear Dimensions", "Outside minor axis diameter")
        obj.addProperty("App::PropertyLength", "MajorRootDiameter", "Gear Dimensions", "Root major axis diameter")
        obj.addProperty("App::PropertyLength", "MinorRootDiameter", "Gear Dimensions", "Root minor axis diameter")
        obj.addProperty("App::PropertyLength", "FocalDistance", "Gear Dimensions", "Distance from geometric center to each focus (c)")

        obj.setEditorMode("MajorOutsideDiameter", 1)
        obj.setEditorMode("MinorOutsideDiameter", 1)
        obj.setEditorMode("MajorRootDiameter", 1)
        obj.setEditorMode("MinorRootDiameter", 1)
        obj.setEditorMode("FocalDistance", 1)

    def execute(self, obj):
        """Recompute the OCC-valid 3D solid whenever any property is changed"""
        Z = max(3, int(obj.Teeth))
        ar = max(0.1, float(obj.AspectRatio))
        m = max(0.001, float(obj.Module))
        thickness = max(0.001, float(obj.Thickness))
        pressure_angle = float(obj.PressureAngle)
        
        bore_radius = max(0.0, float(obj.BoreRadius))
        focus1_radius = max(0.0, float(obj.FocusBore1Radius))
        focus2_radius = max(0.0, float(obj.FocusBore2Radius))
        
        # Target total pitch perimeter: L = pi * m * Z
        L_target = math.pi * m * Z
        
        # Compute unit ellipse perimeter (a = 1.0, b = 1.0 / AR)
        num_samples = 5000
        unit_perimeter = 0.0
        inv_ar = 1.0 / ar
        
        for i in range(num_samples):
            t_prev = i * 2.0 * math.pi / num_samples
            t_curr = (i + 1) * 2.0 * math.pi / num_samples
            t_mid = (t_prev + t_curr) / 2.0
            dt = t_curr - t_prev
            ds = math.sqrt(math.sin(t_mid)**2 + (inv_ar * math.cos(t_mid))**2) * dt
            unit_perimeter += ds
            
        a = L_target / unit_perimeter
        b = a / ar

        # Compute focal distance c = sqrt(a^2 - b^2)
        c = math.sqrt(max(0.0, a**2 - b**2))

        # Update Read-Only Calculated Properties with explicit unit values
        addendum = m
        dedendum = 1.25 * m

        obj.MajorOutsideDiameter = FreeCAD.Units.Quantity(2.0 * (a + addendum), FreeCAD.Units.Length)
        obj.MinorOutsideDiameter = FreeCAD.Units.Quantity(2.0 * (b + addendum), FreeCAD.Units.Length)
        obj.MajorRootDiameter = FreeCAD.Units.Quantity(2.0 * (a - dedendum), FreeCAD.Units.Length)
        obj.MinorRootDiameter = FreeCAD.Units.Quantity(2.0 * (b - dedendum), FreeCAD.Units.Length)
        obj.FocalDistance = FreeCAD.Units.Quantity(c, FreeCAD.Units.Length)
        
        # Build ellipse arc length mapping table
        t_vals = [0.0]
        s_vals = [0.0]
        current_s = 0.0
        
        for i in range(1, num_samples + 1):
            t_prev = (i - 1) * 2.0 * math.pi / num_samples
            t_curr = i * 2.0 * math.pi / num_samples
            t_mid = (t_prev + t_curr) / 2.0
            dt = t_curr - t_prev
            
            ds = math.sqrt(a**2 * math.sin(t_mid)**2 + b**2 * math.cos(t_mid)**2) * dt
            current_s += ds
            t_vals.append(t_curr)
            s_vals.append(current_s)

        L = s_vals[-1]
        p = L / Z
        alpha = math.radians(pressure_angle)

        def get_t_for_s(target_s):
            target_s = target_s % L
            if target_s < 0:
                target_s += L
            idx = bisect.bisect_left(s_vals, target_s)
            if idx == 0:
                return t_vals[0]
            if idx >= len(s_vals):
                return t_vals[-1]
            s0, s1 = s_vals[idx-1], s_vals[idx]
            t0, t1 = t_vals[idx-1], t_vals[idx]
            if s1 == s0:
                return t0
            return t0 + (target_s - s0) / (s1 - s0) * (t1 - t0)

        def get_root_point_global(s_val):
            """Returns precise global vector on the root curve at arc length s_val"""
            t_c = get_t_for_s(s_val)
            Px = a * math.cos(t_c)
            Py = b * math.sin(t_c)
            dx = -a * math.sin(t_c)
            dy = b * math.cos(t_c)
            length = math.sqrt(dx**2 + dy**2)
            Tx = dx / length
            Ty = dy / length
            Nx = -Ty
            Ny = Tx
            Rx = Px + dedendum * Nx
            Ry = Py + dedendum * Ny
            return FreeCAD.Vector(Rx, Ry, 0)

        all_global_points = []

        for i in range(Z):
            s_c = i * p
            t_c = get_t_for_s(s_c)
            
            Px = a * math.cos(t_c)
            Py = b * math.sin(t_c)
            
            dx = -a * math.sin(t_c)
            dy = b * math.cos(t_c)
            length = math.sqrt(dx**2 + dy**2)
            Tx = dx / length
            Ty = dy / length
            
            rho = (a**2 * math.sin(t_c)**2 + b**2 * math.cos(t_c)**2)**1.5 / (a * b)
            R = rho
            
            pitch_angle = math.pi * m / R
            W = pitch_angle / 2.0
            r_a = R + m
            r_d = R - 1.25 * m
            R_b = R * math.cos(alpha)
            
            inv_alpha = math.tan(alpha) - alpha
            theta_0_right = math.pi/2 - W/2 - inv_alpha
            theta_0_left  = math.pi/2 + W/2 + inv_alpha
            
            # Continuous boundary midpoints shared with adjacent teeth
            pt_root_start = get_root_point_global(s_c - p/2.0)
            pt_root_end   = get_root_point_global(s_c + p/2.0)

            if r_d >= R_b:
                phi_min = math.sqrt((r_d/R_b)**2 - 1.0)
                theta_root_left = theta_0_left - (phi_min - math.atan(phi_min))
                theta_root_right = theta_0_right + (phi_min - math.atan(phi_min))
            else:
                phi_min = 0.0
                theta_root_left = theta_0_left
                theta_root_right = theta_0_right
                
            phi_max = math.sqrt((r_a/R_b)**2 - 1.0)
            
            def local_to_global(r, th):
                lx = r * math.cos(th)
                ly = r * math.sin(th) - R
                gx = Px + lx * Tx + ly * Ty
                gy = Py + lx * Ty - ly * Tx
                return FreeCAD.Vector(gx, gy, 0)

            tooth_pts = []

            # 1. Start at exact root boundary midpoint
            tooth_pts.append(pt_root_start)

            # 2. Transition arc to left involute base
            pt_inv_left_base = local_to_global(r_d, theta_root_left)
            num_arc = 4
            for j in range(1, num_arc):
                frac = j / float(num_arc)
                interp_pt = pt_root_start.add(pt_inv_left_base.sub(pt_root_start).multiply(frac))
                tooth_pts.append(interp_pt)

            # 3. Left involute curve
            num_inv = 12
            for j in range(1, num_inv):
                phi = phi_min + (phi_max - phi_min) * j / (num_inv - 1)
                r = R_b * math.sqrt(1 + phi**2)
                th = theta_0_left - (phi - math.atan(phi))
                tooth_pts.append(local_to_global(r, th))

            # 4. Top addendum arc
            theta_left_top = theta_0_left - (phi_max - math.atan(phi_max))
            theta_right_top = theta_0_right + (phi_max - math.atan(phi_max))
            for j in range(1, num_arc):
                th = theta_left_top + (theta_right_top - theta_left_top) * j / (num_arc - 1)
                tooth_pts.append(local_to_global(r_a, th))

            # 5. Right involute curve
            for j in range(1, num_inv):
                phi = phi_max - (phi_max - phi_min) * j / (num_inv - 1)
                r = R_b * math.sqrt(1 + phi**2)
                th = theta_0_right + (phi - math.atan(phi))
                tooth_pts.append(local_to_global(r, th))

            # 6. Transition arc ending at right root boundary midpoint
            pt_inv_right_base = local_to_global(r_d, theta_root_right)
            for j in range(1, num_arc):
                frac = j / float(num_arc)
                interp_pt = pt_inv_right_base.add(pt_root_end.sub(pt_inv_right_base).multiply(frac))
                tooth_pts.append(interp_pt)

            tooth_pts.append(pt_root_end)
            all_global_points.extend(tooth_pts)

        # Remove duplicate points
        cleaned_points = [all_global_points[0]]
        for p_pt in all_global_points[1:]:
            if (p_pt - cleaned_points[-1]).Length > 1e-4:
                cleaned_points.append(p_pt)

        if (cleaned_points[-1] - cleaned_points[0]).Length > 1e-4:
            cleaned_points.append(cleaned_points[0])

        # Construct and repair wire/face topology
        polygon = Part.makePolygon(cleaned_points)
        gear_wire = Part.Wire(polygon)
        gear_wire.fix(1e-3, 1e-3, 1e-3)
        
        final_face = Part.Face(gear_wire)
        final_face.validate()

        # ----------------------------------------------------
        # PROCESS BORE HOLES (Center & Dynamically Updated Foci)
        # ----------------------------------------------------
        bores_to_cut = []

        # Center bore
        if bore_radius > 0.001:
            edge = Part.makeCircle(bore_radius, FreeCAD.Vector(0, 0, 0), FreeCAD.Vector(0, 0, 1))
            bores_to_cut.append(Part.Face(Part.Wire([edge])))

        # Focus 1 (-c, 0)
        if focus1_radius > 0.001 and c > 0.001:
            edge1 = Part.makeCircle(focus1_radius, FreeCAD.Vector(-c, 0, 0), FreeCAD.Vector(0, 0, 1))
            bores_to_cut.append(Part.Face(Part.Wire([edge1])))

        # Focus 2 (+c, 0)
        if focus2_radius > 0.001 and c > 0.001:
            edge2 = Part.makeCircle(focus2_radius, FreeCAD.Vector(c, 0, 0), FreeCAD.Vector(0, 0, 1))
            bores_to_cut.append(Part.Face(Part.Wire([edge2])))

        # Cut all bore holes from main face
        for b_face in bores_to_cut:
            final_face = final_face.cut(b_face)

        # Extrude and clean up coplanar splitters for robust OCC Boolean operations
        gear_solid = final_face.extrude(FreeCAD.Vector(0, 0, thickness))
        try:
            gear_solid = gear_solid.removeSplitter()
        except Exception:
            pass
            
        obj.Shape = gear_solid


class ViewProviderEllipticalGear:
    """View provider class for FreeCAD GUI integration"""
    def __init__(self, vobj):
        vobj.Proxy = self

    def attach(self, vobj):
        self.ViewObject = vobj

    def getDefaultDisplayMode(self):
        return "Shaded"

    def getIcon(self):
        return ""

    def __getstate__(self):
        return None

    def __setstate__(self, state):
        return None


# Explicitly register classes in main module scope
sys.modules['__main__'].EllipticalGear = EllipticalGear
sys.modules['__main__'].ViewProviderEllipticalGear = ViewProviderEllipticalGear


def makeEllipticalGear():
    doc = FreeCAD.activeDocument()
    if doc is None:
        doc = FreeCAD.newDocument("EllipticalGearDoc")
        
    obj = doc.addObject("Part::FeaturePython", "EllipticalGear")
    EllipticalGear(obj)
    
    if FreeCAD.GuiUp and obj.ViewObject is not None:
        ViewProviderEllipticalGear(obj.ViewObject)
        
    doc.recompute()
    if FreeCAD.GuiUp:
        FreeCADGui.SendMsgToActiveView("ViewFit")

if __name__ == "__main__":
    makeEllipticalGear()
